module address-config {
    yang-version 1;
    namespace "urn:opendaylight:params:xml:ns:yang:dipapp:address-config";
    prefix "address-config";

    import ietf-inet-types { prefix inet; }

    import ietf-yang-types {
        prefix yang;
        revision-date 2013-07-15;
    }
    contact "guozhencheng@hotmail.com";
    
    organization "www.ndsc.org";
    
    description " this model is used to config real IP segment.";
    
    revision "2015-01-05";

    typedef state_model{
            type enumeration{
                enum "success"{
                    value 1;
                }
                enum "false"{
                    value 2;
                }
            }
            description "The state of Ip config.";
        }

    grouping addrs-domain {
        
        list ip-conf {
        	key rips-id;
        		
        	leaf rips-id {
                type string;
                description "the real IP segment ID, the length 32 byte.";
            }
    	    leaf rips-name {
    			type string;
    			description "the real IP segment name.";
    	    }
        	
            leaf start-ip {
                type inet:ip-address;
                description "real start Ip of for the subnet.";
            }
            leaf end-ip {
                type inet:ip-address;
                description "real end Ip of for the subnet";
            }
            leaf domain-prefix {
                type string;
                description "The domain prefix of the subnet.";
            }
            leaf ip-global-period {
                type int64;
                description "The global period that real ip segment is mutated.";
            }
        }
    }

    container subnets {
        description "It's a container used to store the virtual address configuration of various subnet";
        
        config true;
        uses addrs-domain;
    }

    rpc subnet-config {
        description "vaddr configuration service";

        input {
            uses addrs-domain;
        }

        output {
            leaf success {
                description "true: success; false: failed.";
                type boolean;
            }
            leaf message {
                description "details information for the result to involve the rpc.";
                type string;
            }
            leaf state {
                description "the output of Ip config's state.";
                type state_model;
            }
        }
    }

    notification addr-segment {
        description "vaddr segment configuration notification.";
        uses addrs-domain;
    } 
}
